import FreeCAD as App,FreeCADGui as Gui
from pathlib import Path
p=Path(__file__).resolve().parent/'Ausgabe/P02_Kaufteile_Integration_GESPERRT.FCStd'
d=App.openDocument(str(p))
for o in d.Objects:
    if hasattr(o,'P02_Klasse'):
        if getattr(o,'BauteilID','').startswith('KEEP_'):o.ViewObject.Visibility=False;continue
        o.ViewObject.ShapeColor=(.22,.7,.4) if o.P02_Klasse=='Importiertes_Normteil' else (.9,.45,.28) if o.P02_Klasse=='Kaufteil_Anschlussreferenz' else (.78,.72,.35)
Gui.activeDocument().activeView().viewAxonometric();Gui.activeDocument().activeView().fitAll()
App.Console.PrintMessage('P02: Grün = maßgeprüfte Normteilreferenz, Orange = Kaufteil-Anschlussdaten offen, Gelb = Eigenfertigungsentwurf. Keine Gesamt-Fertigungsfreigabe.\n')
